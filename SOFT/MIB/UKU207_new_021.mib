UKU207NEW DEFINITIONS ::= BEGIN

IMPORTS
	enterprises
		FROM RFC1155-SMI
	OBJECT-TYPE
		FROM RFC-1212
	TRAP-TYPE
		FROM RFC-1215
	DisplayString
		FROM RFC-1213;


-- Системы ПромАвтоматики

entSPA-SIB           OBJECT IDENTIFIER ::= { enterprises 33183 }
uku207new            OBJECT IDENTIFIER ::= { entSPA-SIB 25 }
displayDeviceInfo    OBJECT IDENTIFIER ::= { uku207new 1 }
dipslayMains         OBJECT IDENTIFIER ::= { uku207new 2 }
displayLoad          OBJECT IDENTIFIER ::= { uku207new 3 }
displaySpecials      OBJECT IDENTIFIER ::= { uku207new 6 }
commands             OBJECT IDENTIFIER ::= { uku207new 8 }
sysParams            OBJECT IDENTIFIER ::= { uku207new 10 }
displayEnergy        OBJECT IDENTIFIER ::= { uku207new 12 }
displayDEBUG         OBJECT IDENTIFIER ::= { uku207new 13 }
displayBYPASS        OBJECT IDENTIFIER ::= { uku207new 19 }

displayDeviceInfoCode  OBJECT-TYPE
	SYNTAX     INTEGER (0..65535)
	ACCESS     read-only
	STATUS     mandatory
	DESCRIPTION 
		""
	::= { displayDeviceInfo 1 }

displayDeviceInfoSerial  OBJECT-TYPE
	SYNTAX     INTEGER (0..65535)
	ACCESS     read-only
	STATUS     mandatory
	DESCRIPTION 
		""
	::= { displayDeviceInfo 2 }

displayDeviceInfoLocation  OBJECT-TYPE
	SYNTAX     DisplayString (SIZE(69))
	ACCESS     read-write
	STATUS     mandatory
	DESCRIPTION 
		""
	::= { displayDeviceInfo 3 }

displayDeviceInfoNumOfBat  OBJECT-TYPE
	SYNTAX     INTEGER
	ACCESS     read-only
	STATUS     mandatory
	DESCRIPTION 
		""
	::= { displayDeviceInfo 4 }

displayDeviceInfoNumOfBps  OBJECT-TYPE
	SYNTAX     INTEGER
	ACCESS     read-only
	STATUS     mandatory
	DESCRIPTION 
		""
	::= { displayDeviceInfo 5 }

displayDeviceInfoNumOfTnv  OBJECT-TYPE
	SYNTAX     INTEGER
	ACCESS     read-only
	STATUS     mandatory
	DESCRIPTION 
		""
	::= { displayDeviceInfo 6 }

displayDeviceInfoNumOfAvt  OBJECT-TYPE
	SYNTAX     INTEGER
	ACCESS     read-only
	STATUS     mandatory
	DESCRIPTION 
		""
	::= { displayDeviceInfo 7 }

displayDeviceInfoNumOfDt  OBJECT-TYPE
	SYNTAX     INTEGER
	ACCESS     read-only
	STATUS     mandatory
	DESCRIPTION 
		""
	::= { displayDeviceInfo 8 }

displayDeviceInfoNumOfSk  OBJECT-TYPE
	SYNTAX     INTEGER
	ACCESS     read-only
	STATUS     mandatory
	DESCRIPTION 
		""
	::= { displayDeviceInfo 9 }

displayDeviceInfoNumOfEvents  OBJECT-TYPE
	SYNTAX     INTEGER
	ACCESS     read-only
	STATUS     mandatory
	DESCRIPTION 
		""
	::= { displayDeviceInfo 10 }

	
displayDeviceInfoModel  OBJECT-TYPE
	SYNTAX     DisplayString (SIZE(69))
	ACCESS     read-write
	STATUS     mandatory
	DESCRIPTION 
		""
	::= { displayDeviceInfo 11 }
	
dipslayMainsVoltage  OBJECT-TYPE
	SYNTAX     INTEGER (0..65535)
	ACCESS     read-only
	STATUS     mandatory
	DESCRIPTION 
		""
	::= { dipslayMains 1 }

dipslayMainsFrequency  OBJECT-TYPE
	SYNTAX     INTEGER (0..65535)
	ACCESS     read-only
	STATUS     mandatory
	DESCRIPTION 
		""
	::= { dipslayMains 2 }

dipslayMainsStatus  OBJECT-TYPE
	SYNTAX     INTEGER (0..65535)
	ACCESS     read-only
	STATUS     mandatory
	DESCRIPTION 
		""
	::= { dipslayMains 3 }

-- //

dipslayMainsAlarm  OBJECT-TYPE
	SYNTAX     INTEGER (0..65535)
	ACCESS     read-only
	STATUS     mandatory
	DESCRIPTION 
		""
	::= { dipslayMains 4 }

dipslayMainsPhaseA  OBJECT-TYPE
	SYNTAX     INTEGER
	ACCESS     read-only
	STATUS     mandatory
	DESCRIPTION 
		""
	::= { dipslayMains 5 }

dipslayMainsPhaseB  OBJECT-TYPE
	SYNTAX     INTEGER
	ACCESS     read-only
	STATUS     mandatory
	DESCRIPTION 
		""
	::= { dipslayMains 6 }

dipslayMainsPhaseC  OBJECT-TYPE
	SYNTAX     INTEGER
	ACCESS     read-only
	STATUS     mandatory
	DESCRIPTION 
		""
	::= { dipslayMains 7 }

displayLoadVoltage  OBJECT-TYPE
	SYNTAX     INTEGER (0..65535)
	ACCESS     read-only
	STATUS     mandatory
	DESCRIPTION 
		""
	::= { displayLoad 1 }

displayLoadCurrent  OBJECT-TYPE
	SYNTAX     INTEGER (0..65535)
	ACCESS     read-only
	STATUS     mandatory
	DESCRIPTION 
		""
	::= { displayLoad 2 }



displayPSUEntry  OBJECT-TYPE
	SYNTAX 	DisplayPSUEntry
	ACCESS     not-accessible
	STATUS     mandatory
	DESCRIPTION 
		"PSU listing"
	INDEX { displayPSUnumber }
	::= { displayPSUTable 1 }

DisplayPSUEntry ::= SEQUENCE {
	displayPSUnumber
		INTEGER,
	displayPSUVoltage
		INTEGER,
	displayPSUCurrent
		INTEGER,
	displayPSUTemperature
		INTEGER,
	displayPSUStatus
		INTEGER
}

displayPSUnumber  OBJECT-TYPE
	SYNTAX     INTEGER
	ACCESS     read-only
	STATUS     mandatory
	DESCRIPTION 
		""
	::= { displayPSUEntry 1 }

displayPSUVoltage  OBJECT-TYPE
	SYNTAX     INTEGER (0..65535)
	ACCESS     read-only
	STATUS     mandatory
	DESCRIPTION 
		""
	::= { displayPSUEntry 2 }

displayPSUCurrent  OBJECT-TYPE
	SYNTAX     INTEGER (0..65535)
	ACCESS     read-only
	STATUS     mandatory
	DESCRIPTION 
		""
	::= { displayPSUEntry 3 }

displayPSUTemperature  OBJECT-TYPE
	SYNTAX     INTEGER (0..65535)
	ACCESS     read-only
	STATUS     mandatory
	DESCRIPTION 
		""
	::= { displayPSUEntry 4 }

displayPSUStatus  OBJECT-TYPE
	SYNTAX     INTEGER (0..65535)
	ACCESS     read-only
	STATUS     mandatory
	DESCRIPTION 
		""
	::= { displayPSUEntry 5 }

displayBatTable  OBJECT-TYPE
	SYNTAX SEQUENCE OF DisplayBatEntry
	ACCESS     not-accessible
	STATUS     mandatory
	DESCRIPTION 
		""
	::= { uku207new 5 }

displayBatEntry  OBJECT-TYPE
	SYNTAX 	DisplayBatEntry
	ACCESS     not-accessible
	STATUS     mandatory
	DESCRIPTION 
		""
	INDEX { displayBatteriesMassNumber }
	::= { displayBatTable 1 }

DisplayBatEntry ::= SEQUENCE {
	displayBatteriesMassNumber
		INTEGER,
	displayBatteriesMassVoltage
		INTEGER,
	displayBatteriesMassCurrent
		INTEGER,
	displayBatteriesMassTemperature
		INTEGER,
	displayBatteriesMassCapacity
		INTEGER,
	displayBatteriesMassCharge
		INTEGER,
	displayBatteriesMassStatus
		INTEGER
}

displayBatteriesMassNumber  OBJECT-TYPE
	SYNTAX     INTEGER
	ACCESS     read-only
	STATUS     mandatory
	DESCRIPTION 
		""
	::= { displayBatEntry 1 }

displayBatteriesMassVoltage  OBJECT-TYPE
	SYNTAX     INTEGER (0..65535)
	ACCESS     read-only
	STATUS     mandatory
	DESCRIPTION 
		""
	::= { displayBatEntry 2 }

displayBatteriesMassCurrent  OBJECT-TYPE
	SYNTAX     INTEGER (0..65535)
	ACCESS     read-only
	STATUS     mandatory
	DESCRIPTION 
		""
	::= { displayBatEntry 3 }

displayBatteriesMassTemperature  OBJECT-TYPE
	SYNTAX     INTEGER (0..65535)
	ACCESS     read-only
	STATUS     mandatory
	DESCRIPTION 
		"battery temperature in degrees Celsius, if the sensor is faulty is -1000 degrees"
	::= { displayBatEntry 4 }

displayBatteriesMassCapacity  OBJECT-TYPE
	SYNTAX     INTEGER (0..65535)
	ACCESS     read-only
	STATUS     mandatory
	DESCRIPTION 
		""
	::= { displayBatEntry 5 }

displayBatteriesMassCharge  OBJECT-TYPE
	SYNTAX     INTEGER (0..65535)
	ACCESS     read-only
	STATUS     mandatory
	DESCRIPTION 
		""
	::= { displayBatEntry 6 }

displayBatteriesMassStatus  OBJECT-TYPE
	SYNTAX     INTEGER (0..65535)
	ACCESS     read-only
	STATUS     mandatory
	DESCRIPTION 
		""
	::= { displayBatEntry 7 }

displayBatteriesMassRemTime  OBJECT-TYPE
	SYNTAX     INTEGER (0..65535)
	ACCESS     read-only
	STATUS     mandatory
	DESCRIPTION 
		"estimated battery discharge time in minutes"
	::= { displayBatEntry 8 }

displayBatteriesMassMidVoltage  OBJECT-TYPE
	SYNTAX     INTEGER (0..65535)
	ACCESS     read-only
	STATUS     mandatory
	DESCRIPTION 
		"Battery Midpoint Voltage"
	::= { displayBatEntry 9 }

displaySpecialsControlByte  OBJECT-TYPE
	SYNTAX     INTEGER (0..65535)
	ACCESS     read-only
	STATUS     mandatory
	DESCRIPTION 
		""
	::= { displaySpecials 1 }

displaySpecialsSpecFunctions  OBJECT-TYPE
	SYNTAX     INTEGER (0..65535)
	ACCESS     read-only
	STATUS     mandatory
	DESCRIPTION 
		""
	::= { displaySpecials 2 }

displayDeviceType  OBJECT-TYPE
	SYNTAX     INTEGER (0..65535)
	ACCESS     read-only
	STATUS     mandatory
	DESCRIPTION 
		""
	::= { displaySpecials 3 }

displaySpecialsTrapMessage  OBJECT-TYPE
	SYNTAX     DisplayString (SIZE(0..30))
	ACCESS     read-only
	STATUS     mandatory
	DESCRIPTION 
		""
	::= { displaySpecials 4 }

displaySpecialsTrapValue  OBJECT-TYPE
	SYNTAX     INTEGER (0..65535)
	ACCESS     read-only
	STATUS     mandatory
	DESCRIPTION 
		""
	::= { displaySpecials 5 }

displaySpecialsCapacityControl  OBJECT-TYPE
	SYNTAX     INTEGER
	ACCESS     read-write
	STATUS     mandatory
	DESCRIPTION 
		""
	::= { displaySpecials 6 }

displaySpecialsCompensationCharge  OBJECT-TYPE
	SYNTAX     INTEGER
	ACCESS     read-write
	STATUS     mandatory
	DESCRIPTION 
		""
	::= { displaySpecials 7 }

sendCommand  OBJECT-TYPE
	SYNTAX     INTEGER (0..65535)
	ACCESS     read-write
	STATUS     mandatory
	DESCRIPTION 
		""
	::= { commands 1 }

commandParameter  OBJECT-TYPE
	SYNTAX     INTEGER (0..65535)
	ACCESS     read-write
	STATUS     mandatory
	DESCRIPTION 
		""
	::= { commands 2 }

commandID  OBJECT-TYPE
	SYNTAX     INTEGER (0..65535)
	ACCESS     read-write
	STATUS     mandatory
	DESCRIPTION 
		""
	::= { commands 3 }

displayEventsTable  OBJECT-TYPE
	SYNTAX SEQUENCE OF DisplayEventsEntry
	ACCESS     not-accessible
	STATUS     mandatory
	DESCRIPTION 
		""
	::= { uku207new 9 }

displayEventsEntry  OBJECT-TYPE
	SYNTAX 	DisplayEventsEntry
	ACCESS     not-accessible
	STATUS     mandatory
	DESCRIPTION 
		""
	INDEX { displayEventNumber }
	::= { displayEventsTable 1 }

DisplayEventsEntry ::= SEQUENCE {
	displayEventNumber
		DisplayString
}

displayEventNumber  OBJECT-TYPE
	SYNTAX     DisplayString
	ACCESS     read-only
	STATUS     mandatory
	DESCRIPTION 
		""
	::= { displayEventsEntry 1 }

sysParamsSoundAlarmEn  OBJECT-TYPE
	SYNTAX     INTEGER
	ACCESS     read-write
	STATUS     mandatory
	DESCRIPTION 
		""
	::= { sysParams 40 }

sysParamsAlarmAutoDisable  OBJECT-TYPE
	SYNTAX     INTEGER
	ACCESS     read-write
	STATUS     mandatory
	DESCRIPTION 
		""
	::= { sysParams 41 }

sysParamsBattTestTime  OBJECT-TYPE
	SYNTAX     INTEGER
	ACCESS     read-write
	STATUS     mandatory
	DESCRIPTION 
		""
	::= { sysParams 42 }

sysParamsUmax  OBJECT-TYPE
	SYNTAX     INTEGER
	ACCESS     read-write
	STATUS     mandatory
	DESCRIPTION 
		""
	::= { sysParams 49 }

sysParamsUmin  OBJECT-TYPE
	SYNTAX     INTEGER
	ACCESS     read-write
	STATUS     mandatory
	DESCRIPTION 
		""
	::= { sysParams 5 }

sysParamsU0  OBJECT-TYPE
	SYNTAX     INTEGER
	ACCESS     read-write
	STATUS     mandatory
	DESCRIPTION 
		""
	::= { sysParams 50 }

sysParamsU20  OBJECT-TYPE
	SYNTAX     INTEGER
	ACCESS     read-write
	STATUS     mandatory
	DESCRIPTION 
		""
	::= { sysParams 51 }

sysParamsUsign  OBJECT-TYPE
	SYNTAX     INTEGER
	ACCESS     read-write
	STATUS     mandatory
	DESCRIPTION 
		""
	::= { sysParams 8 }

sysParamsUminPower  OBJECT-TYPE
	SYNTAX     INTEGER
	ACCESS     read-write
	STATUS     mandatory
	DESCRIPTION 
		""
	::= { sysParams 9 }

sysParamsUWithothBatt  OBJECT-TYPE
	SYNTAX     INTEGER
	ACCESS     read-write
	STATUS     mandatory
	DESCRIPTION 
		""
	::= { sysParams 10 }

sysParamsControlCurrent  OBJECT-TYPE
	SYNTAX     INTEGER
	ACCESS     read-write
	STATUS     mandatory
	DESCRIPTION 
		""
	::= { sysParams 11 }

sysParamsMaxChargeCurrent  OBJECT-TYPE
	SYNTAX     INTEGER
	ACCESS     read-write
	STATUS     mandatory
	DESCRIPTION 
		""
	::= { sysParams 12 }

sysParamsMaxCurrent  OBJECT-TYPE
	SYNTAX     INTEGER
	ACCESS     read-write
	STATUS     mandatory
	DESCRIPTION 
		""
	::= { sysParams 13 }

sysParamsMinCurrent  OBJECT-TYPE
	SYNTAX     INTEGER
	ACCESS     read-write
	STATUS     mandatory
	DESCRIPTION 
		""
	::= { sysParams 14 }

sysParamsUpChargeVoltage  OBJECT-TYPE
	SYNTAX     INTEGER
	ACCESS     read-write
	STATUS     mandatory
	DESCRIPTION 
		""
	::= { sysParams 15 }

sysParamsPowerupPSUTimeout  OBJECT-TYPE
	SYNTAX     INTEGER
	ACCESS     read-write
	STATUS     mandatory
	DESCRIPTION 
		""
	::= { sysParams 16 }

sysParamsBatSignTemperature  OBJECT-TYPE
	SYNTAX     INTEGER
	ACCESS     read-write
	STATUS     mandatory
	DESCRIPTION 
		""
	::= { sysParams 17 }

sysParamsBatMaxTemperature  OBJECT-TYPE
	SYNTAX     INTEGER
	ACCESS     read-write
	STATUS     mandatory
	DESCRIPTION 
		""
	::= { sysParams 18 }

sysParamsBpsSignTemperature  OBJECT-TYPE
	SYNTAX     INTEGER
	ACCESS     read-write
	STATUS     mandatory
	DESCRIPTION 
		""
	::= { sysParams 19 }

sysParamsBpsMaxTemperature  OBJECT-TYPE
	SYNTAX     INTEGER
	ACCESS     read-write
	STATUS     mandatory
	DESCRIPTION 
		""
	::= { sysParams 20 }

sysParamsBatAssimetyAlarmPercent  OBJECT-TYPE
	SYNTAX     INTEGER
	ACCESS     read-write
	STATUS     mandatory
	DESCRIPTION 
		""
	::= { sysParams 21 }

sysParamsPowerCntAdress  OBJECT-TYPE
	SYNTAX     INTEGER
	ACCESS     read-write
	STATUS     mandatory
	DESCRIPTION 
		""
	::= { sysParams 22 }

dysplayAvtTable  OBJECT-TYPE
	SYNTAX SEQUENCE OF DysplayAvtEntry
	ACCESS     not-accessible
	STATUS     mandatory
	DESCRIPTION 
		""
	::= { uku207new 11 }

dysplayAvtEntry  OBJECT-TYPE
	SYNTAX 	DysplayAvtEntry
	ACCESS     not-accessible
	STATUS     mandatory
	DESCRIPTION 
		""
	INDEX { displayPSUnumber }
	::= { dysplayAvtTable 1 }

DysplayAvtEntry ::= SEQUENCE {
	dysplayAvtNumber
		INTEGER,
	dysplayAvtStat
		INTEGER
}

dysplayAvtNumber  OBJECT-TYPE
	SYNTAX     INTEGER
	ACCESS     read-only
	STATUS     mandatory
	DESCRIPTION 
		""
	::= { dysplayAvtEntry 1 }

dysplayAvtStat  OBJECT-TYPE
	SYNTAX     INTEGER
	ACCESS     read-only
	STATUS     mandatory
	DESCRIPTION 
		""
	::= { dysplayAvtEntry 2 }

displayEnergyVvodPhaseA  OBJECT-TYPE
	SYNTAX     INTEGER
	ACCESS     read-only
	STATUS     mandatory
	DESCRIPTION 
		""
	::= { displayEnergy 1 }

displayEnergyVvodPhaseB  OBJECT-TYPE
	SYNTAX     INTEGER
	ACCESS     read-only
	STATUS     mandatory
	DESCRIPTION 
		""
	::= { displayEnergy 2 }

displayEnergyVvodPhaseC  OBJECT-TYPE
	SYNTAX     INTEGER
	ACCESS     read-only
	STATUS     mandatory
	DESCRIPTION 
		""
	::= { displayEnergy 3 }

displayEnergyPesPhaseA  OBJECT-TYPE
	SYNTAX     INTEGER
	ACCESS     read-only
	STATUS     mandatory
	DESCRIPTION 
		""
	::= { displayEnergy 4 }

displayEnergyPesPhaseB  OBJECT-TYPE
	SYNTAX     INTEGER
	ACCESS     read-only
	STATUS     mandatory
	DESCRIPTION 
		""
	::= { displayEnergy 5 }

displayEnergyPesPhaseC  OBJECT-TYPE
	SYNTAX     INTEGER
	ACCESS     read-only
	STATUS     mandatory
	DESCRIPTION 
		""
	::= { displayEnergy 6 }

displayTotalEnergy  OBJECT-TYPE
	SYNTAX     INTEGER
	ACCESS     read-only
	STATUS     mandatory
	DESCRIPTION 
		""
	::= { displayEnergy 7 }

displayCurrentEnergy  OBJECT-TYPE
	SYNTAX     INTEGER
	ACCESS     read-only
	STATUS     mandatory
	DESCRIPTION 
		""
	::= { displayEnergy 8 }

displayDEBUGcommanLength  OBJECT-TYPE
	SYNTAX     INTEGER (0..65535)
	ACCESS     read-write
	STATUS     mandatory
	DESCRIPTION 
		""
	::= { displayDEBUG 1 }

displayDEBUGcommandSENT  OBJECT-TYPE
	SYNTAX     DisplayString (SIZE(0..255))
	ACCESS     read-only
	STATUS     mandatory
	DESCRIPTION 
		""
	::= { displayDEBUG 2 }

displayDEBUGreplyRCVD  OBJECT-TYPE
	SYNTAX     DisplayString (SIZE(0..255))
	ACCESS     read-only
	STATUS     mandatory
	DESCRIPTION 
		""
	::= { displayDEBUG 3 }

displayDEBUGsentPckts  OBJECT-TYPE
	SYNTAX     INTEGER (0..65535)
	ACCESS     read-only
	STATUS     mandatory
	DESCRIPTION 
		""
	::= { displayDEBUG 4 }

displayDEBUGrcvdPckts  OBJECT-TYPE
	SYNTAX     INTEGER (0..65535)
	ACCESS     read-only
	STATUS     mandatory
	DESCRIPTION 
		""
	::= { displayDEBUG 5 }

displayDEBUGSetVar  OBJECT-TYPE
	SYNTAX     INTEGER (0..65535)
	ACCESS     read-write
	STATUS     mandatory
	DESCRIPTION 
		""
	::= { displayDEBUG 6 }

displayINVTable  OBJECT-TYPE
	SYNTAX SEQUENCE OF DisplayINVEntry
	ACCESS     not-accessible
	STATUS     mandatory
	DESCRIPTION 
		""
	::= { uku207new 4 }

displayINVEntry  OBJECT-TYPE
	SYNTAX 	DisplayINVEntry
	ACCESS     not-accessible
	STATUS     mandatory
	DESCRIPTION 
		""
	INDEX { displayINVNumber }
	::= { displayINVTable 1 }

DisplayINVEntry ::= SEQUENCE {
	displayINVNumber
		INTEGER,
	displayINVVoltage
		INTEGER,
	displayINVCourrent
		INTEGER,
	displayINVTemperature
		INTEGER,
	displayINVStatusWord
		INTEGER
	displayINVUin
		INTEGER,
	displayINVUbus
		INTEGER,
	displayINVPout
		INTEGER		
}

displayINVNumber  OBJECT-TYPE
	SYNTAX     INTEGER
	ACCESS     read-only
	STATUS     mandatory
	DESCRIPTION 
		""
	::= { displayINVEntry 1 }

displayINVVoltage  OBJECT-TYPE
	SYNTAX     INTEGER
	ACCESS     read-only
	STATUS     mandatory
	DESCRIPTION 
		""
	::= { displayINVEntry 2 }

displayINVCourrent  OBJECT-TYPE
	SYNTAX     INTEGER
	ACCESS     read-only
	STATUS     mandatory
	DESCRIPTION 
		""
	::= { displayINVEntry 3 }

displayINVTemperature  OBJECT-TYPE
	SYNTAX     INTEGER
	ACCESS     read-only
	STATUS     mandatory
	DESCRIPTION 
		""
	::= { displayINVEntry 4 }

displayINVStatusWord  OBJECT-TYPE
	SYNTAX     INTEGER
	ACCESS     read-only
	STATUS     mandatory
	DESCRIPTION 
		""
	::= { displayINVEntry 5 }

displayINVUin  OBJECT-TYPE
	SYNTAX     INTEGER
	ACCESS     read-only
	STATUS     mandatory
	DESCRIPTION 
		""
	::= { displayINVEntry 6 }
	
displayINVUbus  OBJECT-TYPE
	SYNTAX     INTEGER
	ACCESS     read-only
	STATUS     mandatory
	DESCRIPTION 
		""
	::= { displayINVEntry 7 }

displayINVPout  OBJECT-TYPE
	SYNTAX     INTEGER
	ACCESS     read-only
	STATUS     mandatory
	DESCRIPTION 
		""
	::= { displayINVEntry 8 }
	
displaySKTable  OBJECT-TYPE
	SYNTAX SEQUENCE OF DisplaySKEntry
	ACCESS     not-accessible
	STATUS     mandatory
	DESCRIPTION 
		""
	::= { uku207new 15 }

displaySKEntry  OBJECT-TYPE
	SYNTAX 	DisplaySKEntry
	ACCESS     not-accessible
	STATUS     mandatory
	DESCRIPTION 
		""
	INDEX { displaySKNumber }
	::= { displaySKTable 1 }

DisplaySKEntry ::= SEQUENCE {
	displaySKNumber
		INTEGER,
	displaySKAktivity
		INTEGER,
	displaySKAlarmAktivity
		INTEGER,
	displaySKAlarm
		INTEGER
}

displaySKNumber  OBJECT-TYPE
	SYNTAX     INTEGER
	ACCESS     read-only
	STATUS     mandatory
	DESCRIPTION 
		""
	::= { displaySKEntry 1 }

displaySKAktivity  OBJECT-TYPE
	SYNTAX     INTEGER
	ACCESS     read-only
	STATUS     mandatory
	DESCRIPTION 
		""
	::= { displaySKEntry 2 }

displaySKAlarmAktivity  OBJECT-TYPE
	SYNTAX     INTEGER
	ACCESS     read-write
	STATUS     mandatory
	DESCRIPTION 
		""
	::= { displaySKEntry 3 }

displaySKAlarm  OBJECT-TYPE
	SYNTAX     INTEGER
	ACCESS     read-only
	STATUS     mandatory
	DESCRIPTION 
		""
	::= { displaySKEntry 4 }

displayMakbTable  OBJECT-TYPE
	SYNTAX SEQUENCE OF DisplayMakbEntry
	ACCESS     not-accessible
	STATUS     mandatory
	DESCRIPTION 
		""
	::= { uku207new 16 }

displayMakbEntry  OBJECT-TYPE
	SYNTAX 	DisplayMakbEntry
	ACCESS     not-accessible
	STATUS     mandatory
	DESCRIPTION 
		""
	INDEX { displayMakbNumber }
	::= { displayMakbTable 1 }

DisplayMakbEntry ::= SEQUENCE {
	displayMakbNumber
		INTEGER,
	displayMakbConnectStat
		INTEGER,
	displayMakbVoltage1
		INTEGER,
	displayMakbVoltage2
		INTEGER,
	displayMakbVoltage3
		INTEGER,
	displayMakbVoltage4
		INTEGER,
	displayMakbVoltage5
		INTEGER,
	displayMakbTemper1
		INTEGER,
	displayMakbTemper2
		INTEGER,
	displayMakbTemper3
		INTEGER,
	displayMakbTemper4
		INTEGER,
	displayMakbTemper5
		INTEGER,
	displayMakbTemperStat1
		INTEGER,
	displayMakbTemperStat2
		INTEGER,
	displayMakbTemperStat3
		INTEGER,
	displayMakbTemperStat4
		INTEGER,
	displayMakbTemperStat5
		INTEGER
}

displayMakbNumber  OBJECT-TYPE
	SYNTAX     INTEGER
	ACCESS     read-only
	STATUS     mandatory
	DESCRIPTION 
		""
	::= { displayMakbEntry 1 }

displayMakbConnectStat  OBJECT-TYPE
	SYNTAX     INTEGER
	ACCESS     read-only
	STATUS     mandatory
	DESCRIPTION 
		""
	::= { displayMakbEntry 2 }

displayMakbVoltage1  OBJECT-TYPE
	SYNTAX     INTEGER
	ACCESS     read-only
	STATUS     mandatory
	DESCRIPTION 
		""
	::= { displayMakbEntry 3 }

displayMakbVoltage2  OBJECT-TYPE
	SYNTAX     INTEGER
	ACCESS     read-only
	STATUS     mandatory
	DESCRIPTION 
		""
	::= { displayMakbEntry 4 }

displayMakbVoltage3  OBJECT-TYPE
	SYNTAX     INTEGER
	ACCESS     read-only
	STATUS     mandatory
	DESCRIPTION 
		""
	::= { displayMakbEntry 5 }

displayMakbVoltage4  OBJECT-TYPE
	SYNTAX     INTEGER
	ACCESS     read-only
	STATUS     mandatory
	DESCRIPTION 
		""
	::= { displayMakbEntry 6 }

displayMakbVoltage5  OBJECT-TYPE
	SYNTAX     INTEGER
	ACCESS     read-only
	STATUS     mandatory
	DESCRIPTION 
		""
	::= { displayMakbEntry 7 }

displayMakbTemper1  OBJECT-TYPE
	SYNTAX     INTEGER
	ACCESS     read-only
	STATUS     mandatory
	DESCRIPTION 
		""
	::= { displayMakbEntry 8 }

displayMakbTemper2  OBJECT-TYPE
	SYNTAX     INTEGER
	ACCESS     read-only
	STATUS     mandatory
	DESCRIPTION 
		""
	::= { displayMakbEntry 9 }

displayMakbTemper3  OBJECT-TYPE
	SYNTAX     INTEGER
	ACCESS     read-only
	STATUS     mandatory
	DESCRIPTION 
		""
	::= { displayMakbEntry 10 }

displayMakbTemper4  OBJECT-TYPE
	SYNTAX     INTEGER
	ACCESS     read-only
	STATUS     mandatory
	DESCRIPTION 
		""
	::= { displayMakbEntry 11 }

displayMakbTemper5  OBJECT-TYPE
	SYNTAX     INTEGER
	ACCESS     read-only
	STATUS     mandatory
	DESCRIPTION 
		""
	::= { displayMakbEntry 12 }

displayMakbTemperStat1  OBJECT-TYPE
	SYNTAX     INTEGER
	ACCESS     read-only
	STATUS     mandatory
	DESCRIPTION 
		""
	::= { displayMakbEntry 13 }

displayMakbTemperStat2  OBJECT-TYPE
	SYNTAX     INTEGER
	ACCESS     read-only
	STATUS     mandatory
	DESCRIPTION 
		""
	::= { displayMakbEntry 14 }

displayMakbTemperStat3  OBJECT-TYPE
	SYNTAX     INTEGER
	ACCESS     read-only
	STATUS     mandatory
	DESCRIPTION 
		""
	::= { displayMakbEntry 15 }

displayMakbTemperStat4  OBJECT-TYPE
	SYNTAX     INTEGER
	ACCESS     read-only
	STATUS     mandatory
	DESCRIPTION 
		""
	::= { displayMakbEntry 16 }

displayMakbTemperStat5  OBJECT-TYPE
	SYNTAX     INTEGER
	ACCESS     read-only
	STATUS     mandatory
	DESCRIPTION 
		""
	::= { displayMakbEntry 17 }

displayDTTable  OBJECT-TYPE
	SYNTAX SEQUENCE OF DisplayDTEntry
	ACCESS     not-accessible
	STATUS     mandatory
	DESCRIPTION 
		""
	::= { uku207new 17 }

displayDTEntry  OBJECT-TYPE
	SYNTAX 	DisplayDTEntry
	ACCESS     not-accessible
	STATUS     mandatory
	DESCRIPTION 
		""
	INDEX { displayDTNumber }
	::= { displayDTTable 1 }

DisplayDTEntry ::= SEQUENCE {
	displayDTNumber
		INTEGER,
	displayDTTemperature
		INTEGER
}

displayDTNumber  OBJECT-TYPE
	SYNTAX     INTEGER
	ACCESS     read-only
	STATUS     mandatory
	DESCRIPTION 
		""
	::= { displayDTEntry 1 }

displayDTTemperature  OBJECT-TYPE
	SYNTAX     INTEGER
	ACCESS     read-only
	STATUS     mandatory
	DESCRIPTION 
		""
	::= { displayDTEntry 2 }
	
	
displayLiBatTable  OBJECT-TYPE
	SYNTAX SEQUENCE OF DisplayLBTEntry
	ACCESS     not-accessible
	STATUS     mandatory
	DESCRIPTION 
		""
	::= { uku207new 18 }

displayLBTEntry  OBJECT-TYPE
	SYNTAX 	DisplayLBTEntryTEntry
	ACCESS     not-accessible
	STATUS     mandatory
	DESCRIPTION 
		""
	INDEX { displayLBTNumber }
	::= { displayLiBatTable 1 }

DisplayLBTEntry ::= SEQUENCE {
	displayLBTNumber
		INTEGER,
	displayLBTmaxcellvoltage
		INTEGER
	displayLBTmincellvoltage
		INTEGER
	displayLBTmaxcelltemperature
		INTEGER
	displayLBTmincelltemperature
		INTEGER		
	displayLBTVoltage
		INTEGER
	displayLBTChargeCurrent
		INTEGER
	displayLBTDischargeCurrent
		INTEGER	
	displayLBTRatedCapacity  
		INTEGER
	displayLBTSOH  
		INTEGER
	displayLBTSOC  
		INTEGER
	displayLBTChargecurrentlimitingvalue  
		INTEGER
	displayLBTResidualbackuptime  
		SINTEGER
	displayLBTFlags1  
		INTEGER
	displayLBTFlags2  
		INTEGER	
	displayLBTDump1
		DisplayString
	displayLBTDump2
		DisplayString
	displayLBTDump3
		DisplayString
	displayLBTDump4
		DisplayString
	displayLBTDump5
		DisplayString

displayLBTNumber  OBJECT-TYPE
	SYNTAX     INTEGER
	ACCESS     read-only
	STATUS     mandatory
	DESCRIPTION 
		""
	::= { displayLBTEntry 1 }

displayLBTmaxcellvoltage  OBJECT-TYPE
	SYNTAX     INTEGER
	ACCESS     read-only
	STATUS     mandatory
	DESCRIPTION 
		""
	::= { displayLBTEntry 2 }
	
displayLBTmincellvoltage  OBJECT-TYPE
	SYNTAX     INTEGER
	ACCESS     read-only
	STATUS     mandatory
	DESCRIPTION 
		""
	::= { displayLBTEntry 3 }	

displayLBTmaxcelltemperature  OBJECT-TYPE
	SYNTAX     INTEGER
	ACCESS     read-only
	STATUS     mandatory
	DESCRIPTION 
		""
	::= { displayLBTEntry 4 }
	
displayLBTmincelltemperature  OBJECT-TYPE
	SYNTAX     INTEGER
	ACCESS     read-only
	STATUS     mandatory
	DESCRIPTION 
		""
	::= { displayLBTEntry 5 }
	
displayLBTVoltage  OBJECT-TYPE
	SYNTAX     INTEGER
	ACCESS     read-only
	STATUS     mandatory
	DESCRIPTION 
		""
	::= { displayLBTEntry 6 }	

displayLBTChargeCurrent  OBJECT-TYPE
	SYNTAX     INTEGER
	ACCESS     read-only
	STATUS     mandatory
	DESCRIPTION 
		""
	::= { displayLBTEntry 7 }
	
displayLBTDischargeCurrent  OBJECT-TYPE
	SYNTAX     INTEGER
	ACCESS     read-only
	STATUS     mandatory
	DESCRIPTION 
		""
	::= { displayLBTEntry 8 }

displayLBTRatedCapacity  OBJECT-TYPE
	SYNTAX     INTEGER
	ACCESS     read-only
	STATUS     mandatory
	DESCRIPTION 
		""
	::= { displayLBTEntry 9 }

displayLBTSOH  OBJECT-TYPE
	SYNTAX     INTEGER
	ACCESS     read-only
	STATUS     mandatory
	DESCRIPTION 
		""
	::= { displayLBTEntry 10 }

displayLBTSOC  OBJECT-TYPE
	SYNTAX     INTEGER
	ACCESS     read-only
	STATUS     mandatory
	DESCRIPTION 
		""
	::= { displayLBTEntry 11 }

displayLBTChargecurrentlimitingvalue  OBJECT-TYPE
	SYNTAX     INTEGER
	ACCESS     read-only
	STATUS     mandatory
	DESCRIPTION 
		""
	::= { displayLBTEntry 12 }

displayLBTResidualbackuptime  OBJECT-TYPE
	SYNTAX     INTEGER
	ACCESS     read-only
	STATUS     mandatory
	DESCRIPTION 
		""
	::= { displayLBTEntry 13 }

displayLBTFlags1  OBJECT-TYPE
	SYNTAX     INTEGER
	ACCESS     read-only
	STATUS     mandatory
	DESCRIPTION 
		""
	::= { displayLBTEntry 14 }

displayLBTFlags2  OBJECT-TYPE
	SYNTAX     INTEGER
	ACCESS     read-only
	STATUS     mandatory
	DESCRIPTION 
		""
	::= { displayLBTEntry 15 }	
	
displayLBTDump1 OBJECT-TYPE
	SYNTAX     DisplayString (SIZE(10))
	ACCESS     read-only
	STATUS     mandatory
	DESCRIPTION 
		"otladka"
	::= { displayLBTEntry 16 }	

displayLBTDump2 OBJECT-TYPE
	SYNTAX     DisplayString (SIZE(10))
	ACCESS     read-only
	STATUS     mandatory
	DESCRIPTION 
		"otladka"
	::= { displayLBTEntry 17 }
	
displayLBTDump3 OBJECT-TYPE
	SYNTAX     DisplayString (SIZE(10))
	ACCESS     read-only
	STATUS     mandatory
	DESCRIPTION 
		"otladka"
	::= { displayLBTEntry 18 }	
	
displayLBTDump4 OBJECT-TYPE
	SYNTAX     DisplayString (SIZE(10))
	ACCESS     read-only
	STATUS     mandatory
	DESCRIPTION 
		"otladka"
	::= { displayLBTEntry 19 }

displayLBTDump5 OBJECT-TYPE
	SYNTAX     DisplayString (SIZE(10))
	ACCESS     read-only
	STATUS     mandatory
	DESCRIPTION 
		"otladka"
	::= { displayLBTEntry 20 }


displayBypassUload  OBJECT-TYPE
	SYNTAX     INTEGER (0..65535)
	ACCESS     read-only
	STATUS     mandatory
	DESCRIPTION 
		""
	::= { displayBYPASS 1 }

displayBypassILoad  OBJECT-TYPE
	SYNTAX     INTEGER (0..65535)
	ACCESS     read-only
	STATUS     mandatory
	DESCRIPTION 
		""
	::= { displayBYPASS 2 }

displayBypassPLoad  OBJECT-TYPE
	SYNTAX     INTEGER (0..65535)
	ACCESS     read-only
	STATUS     mandatory
	DESCRIPTION 
		""
	::= { displayBYPASS 3 }
	
displayBypassTemper  OBJECT-TYPE
	SYNTAX     INTEGER (0..65535)
	ACCESS     read-only
	STATUS     mandatory
	DESCRIPTION 
		""
	::= { displayBYPASS 4 }

displayBypassUin  OBJECT-TYPE
	SYNTAX     INTEGER (0..65535)
	ACCESS     read-only
	STATUS     mandatory
	DESCRIPTION 
		""
	::= { displayBYPASS 5 }

displayBypassUBus  OBJECT-TYPE
	SYNTAX     INTEGER (0..65535)
	ACCESS     read-only
	STATUS     mandatory
	DESCRIPTION 
		""
	::= { displayBYPASS 6 }	

displayBypassFlags  OBJECT-TYPE
	SYNTAX     INTEGER (0..65535)
	ACCESS     read-only
	STATUS     mandatory
	DESCRIPTION 
		""
	::= { displayBYPASS 7 }	

displayBypassUdcin  OBJECT-TYPE
	SYNTAX     INTEGER (0..65535)
	ACCESS     read-only
	STATUS     mandatory
	DESCRIPTION 
		""
	::= { displayBYPASS 8 }	
	
messageTrap  TRAP-TYPE
	ENTERPRISE entSPA-SIB
	VARIABLES { displaySpecialsTrapMessage }
	DESCRIPTION 
		"Simple Message Trap"
	::= 1

informationTrap  TRAP-TYPE
	ENTERPRISE entSPA-SIB
	VARIABLES { displaySpecialsTrapMessage, 
		displaySpecialsTrapValue }
	DESCRIPTION 
		"This is the information trap
		Messages are
		Alarm serial connection
		Stop alarm serial connection"
	::= 2

alarmTrap  TRAP-TYPE
	ENTERPRISE entSPA-SIB
	VARIABLES { displaySpecialsTrapMessage, 
		displaySpecialsTrapValue }
	DESCRIPTION 
		"Messages:
		Alarm Input Power System 
		Clear Alarm Input Power System
		Alarm Battery x       - Battery Lost!
		Clear Alarm Battery x   - x - battery's number
		Battery x is charging
		Battery x is not charging
		Alarm Overheat PSU x - x number of PSU
		Clear Alarm Overheat PSU x
		Alarm Low Voltage PSU x
		Clear Alarm Low Voltage PSU x
		Alarm High Voltage PSU x
		Clear Alarm High Voltage PSU x
		Alarm No Connection PSUx
		Clear Alarm No Connection PSUx
		PSU x Locked
		PSU x Unlocked
		PSU x In Reserve
		PSU x Not In Reserve
		Compensation Charge Activated
		Battery x Capacity Control
		Special Functions Disabled"
	::= 3
END


-- This MIB was created using NuDesign Team's Visual MIBuilder (Ver 4.7).
